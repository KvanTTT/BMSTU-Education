(defun model10 ()
  (initget  1)
  (setq Center(getpoint "\nEnter center "))
  (setq DBig(getdist "\nEnter D "))
  (setq dSmall(getdist "\Enter d "))
  (while (>= dSmall DBig)
    (setq d(getdist "Error: d < D \nEnter d "))
  )
  (setq m(getdist "\Enter m "))
  (while (< m 1.0)
    (setq m(getdist "Error: m >= 1 \nEnter m "))
  )
  (setq n(getdist "\Enter n "))
  (while (< n 0.0)
    (setq n(getdist "Error: n >= 0, n < 1 \nEnter n "))
  )
  (while (>= n 1.0)
    (setq n(getdist "Error: n >= 0, n < 1 \nEnter n "))
  )
  

  (setq DMax(* m DBig))
  (setq DMin(* n DBig))
  (setq DMax2(/ DMax 2))
  (setq DMin2(/ DMin 2))
  (setq DBig2(/ DBig 2))
  (setq dSmall2(/ dSmall 2))
  (command "_circle" Center  DMax2)
  (cond ((/= DMin 0)
	 (command "_rectang" (list (- (car Center) DMin2) (- (cadr Center) DMin2)) (list (+ (car Center) DMin2) (+ (cadr Center) DMin2)))  
	 ))
  (setq c1(list (- (car Center) DBig2) (cadr Center)))
  (setq c2(list (+ (car Center) DBig2) (cadr Center)))
  (setq c3(list (car Center) (- (cadr Center) DBig2)))
  (setq c4(list (car Center) (+ (cadr Center) DBig2)))
  (command "_circle" c1 "_d"  dSmall)
  (command "_circle" c2  "_d"  dSmall)
  (command "_circle" c3  "_d"  dSmall)
  (command "_circle" c4  "_d"  dSmall)
  (setq c11(list (+ (car c1) dSmall2)  (cadr c1)))
  (setq c21(list (- (car c2) dSmall2)  (cadr c2)))
  (setq c31(list (car c3)  (+ (cadr c3) dSmall2)))
  (setq c41(list (car c4)  (+ (cadr c4) dSmall2)))
  (setq c51(list (+ (car Center) DMax2)  (cadr Center)))
  
  (command "_region" c11 c21 c31 c41 c51"")
  (command "_subtract" c51 ""c11 c21 c31 c41"")
  )
